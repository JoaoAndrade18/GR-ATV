CUSTOM-CONTROL-MIB DEFINITIONS ::= BEGIN

IMPORTS
    MODULE-IDENTITY, OBJECT-TYPE, NOTIFICATION-TYPE,
    enterprises, Integer32, Gauge32, TimeTicks  FROM SNMPv2-SMI
    DisplayString                               FROM SNMPv2-TC;

customControlMIB MODULE-IDENTITY
    LAST-UPDATED "202505200000Z"
    ORGANIZATION "Atividade Pratica GR-2025.2"
    CONTACT-INFO "aluno@exemplo.com"
    DESCRIPTION  "MIB para controle de servicos e monitoramento."
    REVISION     "202505200000Z"
    DESCRIPTION  "Versao corrigida."
    ::= { enterprises 99999 }



-- Objetos Base
control      OBJECT IDENTIFIER ::= { customControlMIB 1 }
controlGroup OBJECT IDENTIFIER ::= { control 1 }
table        OBJECT IDENTIFIER ::= { customControlMIB 2 }
myTraps      OBJECT IDENTIFIER ::= { customControlMIB 0 }



-- Tarefa #01: Objeto de Controle [cite: 3]
snmpdStatus OBJECT-TYPE
    SYNTAX      INTEGER { running(1), stopped(2) }
    MAX-ACCESS  read-only
    STATUS      current
    DESCRIPTION "Estado atual do servico"
    ::= { control 1 }

snmpdAction OBJECT-TYPE
    SYNTAX      INTEGER { stop(1), restart(2), start(3) }
    MAX-ACCESS  read-write
    STATUS      current
    DESCRIPTION "Comando para parar ou reiniciar" [cite: 3, 5]
    ::= { control 2 }

snmpdUptime OBJECT-TYPE
    SYNTAX      DisplayString
    MAX-ACCESS  read-only
    STATUS      current
    DESCRIPTION "Timestamp de quando o servico iniciou"
    ::= { controlGroup 3 }

snmpdVersion OBJECT-TYPE
    SYNTAX      DisplayString
    MAX-ACCESS  read-only
    STATUS      current
    DESCRIPTION "Versao do binario snmpd"
    ::= { controlGroup 4 }


-- Tarefa #02: Tabela de Processos [cite: 9]
processTable OBJECT-TYPE
    SYNTAX      SEQUENCE OF ProcessEntry
    MAX-ACCESS  not-accessible
    STATUS      current
    DESCRIPTION "Tabela de processos com PID, Nome, CPU, Memoria e Uptime[cite: 12]."
    ::= { customControlMIB 2 }

processEntry OBJECT-TYPE
    SYNTAX      ProcessEntry
    MAX-ACCESS  not-accessible
    STATUS      current
    INDEX       { procPID }
    ::= { processTable 1 }

ProcessEntry ::= SEQUENCE {
    procPID         Integer32,
    procName        DisplayString,
    procCPU         Gauge32,
    procMemory      Gauge32,
    procUptime      TimeTicks
}

procPID OBJECT-TYPE
    SYNTAX      Integer32
    MAX-ACCESS  read-only
    STATUS      current
    DESCRIPTION "Indice: PID do processo[cite: 11]."
    ::= { processEntry 1 }

procName OBJECT-TYPE
    SYNTAX      DisplayString
    MAX-ACCESS  read-only
    STATUS      current
    ::= { processEntry 2 }

procCPU OBJECT-TYPE
    SYNTAX      Gauge32
    MAX-ACCESS  read-only
    STATUS      current
    ::= { processEntry 3 }

procMemory OBJECT-TYPE
    SYNTAX      Gauge32
    MAX-ACCESS  read-only
    STATUS      current
    ::= { processEntry 4 }

procUptime OBJECT-TYPE
    SYNTAX      TimeTicks
    MAX-ACCESS  read-only
    STATUS      current
    ::= { processEntry 5 }

-- Tarefa #03: Traps [cite: 16]
myTraps OBJECT IDENTIFIER ::= { customControlMIB 0 }

myHighTemperatureTrap NOTIFICATION-TYPE
    STATUS      current
    DESCRIPTION "Temperatura > 70C[cite: 15]."
    ::= { myTraps 1 }

myDiskFullTrap NOTIFICATION-TYPE
    STATUS      current
    DESCRIPTION "Disco > 95%[cite: 15]."
    ::= { myTraps 2 }

END
